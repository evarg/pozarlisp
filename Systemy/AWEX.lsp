(ssp:Log (strcat " - Strat wczytywanie systemu: " SYSTEM_NAME))

(setq AWEX_PATH_BLOKI (strcat PATH_SKRYPT "Systemy\\AWEX\\"))

(setq LISTA_ELEMENTOW_AWEX '(
"AWEX_MUL"
"AWEX_OPT"
"AWEX_ROP"
"AWEX_TERM"
"AWEX_022"
))
